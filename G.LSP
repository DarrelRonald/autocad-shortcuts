(vmon)
(defun c:g ()
        (setvar "cmdecho" 0)        
        (grtext -1 "Layer/color/ltype to selected object")
        (grtext -2 "  G J Lebbink A.T.A. Delft")
        (setq b (cdr (assoc '8 (setq f1 (entget (car (entsel (strcat " Layer/color/ltype of ...." "<" (getvar "clayer") ">" "?"))))))))
        (command "layer" "s" b "")
         (setq f (cdr (assoc '62 f1)))
         (if (not f) (setq f "bylayer"))             
        (command "color" f)
        (setq f (cdr (assoc '6 f1)))
        (if (not f) (setq f "bylayer"))             
        (command "linetype" "s" f "")
        (setvar "cmdecho" 1)
        (grtext)
        (prin1)
)
