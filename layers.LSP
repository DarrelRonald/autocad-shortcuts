(vmon)
(defun c:FE (/ a b c d e x)
        (setvar "cmdecho" 0)
        (grtext -1 "Freeze layer except....")
        (prompt "\n Freeze layer except....")
        (setq a (ssget)
              b (entget (ssname a 0))
              x 1
              c (cdr (assoc '8 b))
              e c
              d (ssname a 1)
              )
        (while d
            (progn
            (setq b (entget d)
                  c (strcat c "," (cdr (assoc '8 b)))
                  b (entget d)
                  d (ssname a x)
                  x (1+ x)
                  )
            )
        )
        (command "layer" "s" e "f" "*" "t" c "")
        (setvar "cmdecho" 1)
        (grtext)
        (prin1)
)


(defun c:FL (/ a b c d e x)
        (setvar "cmdecho" 0)
        (prompt "\n Freeze layer :")
        (setq a (ssget)
              b (entget (ssname a 0))
              x 1
              c (cdr (assoc '8 b))
              d (ssname a 1)
              )
        (while d
            (progn
            (setq b (entget d)
                  c (strcat c "," (cdr (assoc '8 b)))
                  b (entget d)
                  d (ssname a x)
                  x (1+ x)
                  )
            )
        )
        (command "layer" "f" c "")
        (prompt (strcat "\n Layer(s) " c " frozen"))
        (setvar "cmdecho" 1)
        (grtext)
        (prin1)
)

(defun c:OL (/ a b c d e x)
        (setvar "cmdecho" 0)
        (grtext -1 "OFF layer")
        (grtext -2 " G J Lebbink & F W Blok")
        (prompt "\n Layer to turn OFF:")
        (setq a (ssget)
              b (entget (ssname a 0))
              x 1
              c (cdr (assoc '8 b))
              d (ssname a 1)
              )
        (while d
            (progn
            (setq b (entget d)
                  c (strcat c "," (cdr (assoc '8 b)))
                  b (entget d)
                  d (ssname a x)
                  x (1+ x)
                  )
            )
        )
        (command "layer" "off" c "")
        (prompt (strcat "\n Layer(s) " c " off"))
        (setvar "cmdecho" 1)
        (grtext)
        (prin1)
)
